(defun c:test2d_0_180 ()
    (setq cen (list 0.0 0.0))
    (setq res (entmake (list '(0 . "ARC") (cons 10 cen) (cons 40 10.0) (cons 50 0.0) (cons 51 3.14159265))))
    (if res (princ "\nSuccess: Created 2D 0->180") (princ "\nFailed: 2D 0->180 returned nil"))
    (princ)
)

(defun c:test2d_180_360 ()
    (setq cen (list 40.0 0.0))
    (setq res (entmake (list '(0 . "ARC") (cons 10 cen) (cons 40 10.0) (cons 50 3.14159265) (cons 51 6.2831853))))
    (if res (princ "\nSuccess: Created 2D 180->360") (princ "\nFailed: 2D 180->360 returned nil"))
    (princ)
)

(defun c:test2d_90_270 ()
    (setq cen (list 80.0 0.0))
    (setq res (entmake (list '(0 . "ARC") (cons 10 cen) (cons 40 10.0) (cons 50 1.5707963) (cons 51 4.7123889))))
    (if res (princ "\nSuccess: Created 2D 90->270") (princ "\nFailed: 2D 90->270 returned nil"))
    (princ)
)

(defun c:test2d_270_90 ()
    (setq cen (list 120.0 0.0))
    (setq res (entmake (list '(0 . "ARC") (cons 10 cen) (cons 40 10.0) (cons 50 4.7123889) (cons 51 1.5707963))))
    (if res (princ "\nSuccess: Created 2D 270->90") (princ "\nFailed: 2D 270->90 returned nil"))
    (princ)
)


(defun c:test3d_0_180 ()
    (setq cen (list 0.0 40.0 0.0))
    (setq res (entmake (list '(0 . "ARC") (cons 10 cen) (cons 40 10.0) (cons 50 0.0) (cons 51 3.14159265))))
    (if res (princ "\nSuccess: Created 3D 0->180") (princ "\nFailed: 3D 0->180 returned nil"))
    (princ)
)

(defun c:test3d_180_360 ()
    (setq cen (list 40.0 40.0 0.0))
    (setq res (entmake (list '(0 . "ARC") (cons 10 cen) (cons 40 10.0) (cons 50 3.14159265) (cons 51 6.2831853))))
    (if res (princ "\nSuccess: Created 3D 180->360") (princ "\nFailed: 3D 180->360 returned nil"))
    (princ)
)

(defun c:test3d_90_270 ()
    (setq cen (list 80.0 40.0 0.0))
    (setq res (entmake (list '(0 . "ARC") (cons 10 cen) (cons 40 10.0) (cons 50 1.5707963) (cons 51 4.7123889))))
    (if res (princ "\nSuccess: Created 3D 90->270") (princ "\nFailed: 3D 90->270 returned nil"))
    (princ)
)

(defun c:test3d_270_90 ()
    (setq cen (list 120.0 40.0 0.0))
    (setq res (entmake (list '(0 . "ARC") (cons 10 cen) (cons 40 10.0) (cons 50 4.7123889) (cons 51 1.5707963))))
    (if res (princ "\nSuccess: Created 3D 270->90") (princ "\nFailed: 3D 270->90 returned nil"))
    (princ)
)

(defun c:testreal ()
    (setq pt (list 0.0 0.0 0.0))
    (setq cen (list (+ (car pt) -50.0000) (+ (cadr pt) -120.0000)))
    (setq res (entmake (list '(0 . "ARC")
                             '(8 . "0")
                             (cons 10 cen)
                             (cons 40 9.5250)
                             (cons 50 0.0000)
                             (cons 51 3.14159265))))
    (if res (princ "\nSuccess: Created testreal") (princ "\nFailed: testreal returned nil"))
    (princ)
)


(defun c:testall ()
    (c:test2d_0_180)
    (c:test2d_180_360)
    (c:test2d_90_270)
    (c:test2d_270_90)
    (c:test3d_0_180)
    (c:test3d_180_360)
    (c:test3d_90_270)
    (c:test3d_270_90)
    (c:testreal)
    (princ "\nDone.")
    (princ)
)

(princ "\nLoad successful. Type (c:testall) or testall to run all tests.")
(princ)
